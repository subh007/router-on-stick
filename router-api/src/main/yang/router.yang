module router {
    yang-version 1;
    namespace "urn:opendaylight:params:xml:ns:yang:router";
    prefix "router";

    import opendaylight-inventory {prefix inv;revision-date "2013-08-19";}

    revision "2015-01-05" {
        description "Initial revision of router model";
    }

    container address-mapping-elem {
        leaf ip {
            description "ip address of the node.";
            type string;
        }

        leaf mac {
            description "mac address of the node.";
            type string;
        }

        leaf in-port {
            description "host is connected to the in-port.";
                type inv:node-connector-ref;
        }

        leaf vlan {
            description "assosiated vlan.";
            type uint16;
        }
    }

    container subinterfaces {
        list sub-interface{
            key "interface";

            leaf interface {
                type string;
            }

            leaf vlan {
                type uint16;
            }

            leaf ip {
                type string;  //place holder
            }

            leaf mac {
                type string; //place holder
            }

            leaf-list port{
                type uint16;
            }
        }
    }
}
